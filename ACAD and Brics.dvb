Attribute VB_Name = "Modulo1"
'//The Structure
#If VBA7 Then
Private Type OPENFILENAME
    lStructSize As Long
    hwndOwner As LongPtr
    hInstance As LongPtr
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long 'LongPtr
    lpfnHook As LongPtr
    lpTemplateName As String
End Type
#Else
Private Type OPENFILENAME
    lStructSize As Long
    hwndOwner As Long
    hInstance As Long
    lpstrFilter As String
    lpstrCustomFilter As String
    nMaxCustFilter As Long
    nFilterIndex As Long
    lpstrFile As String
    nMaxFile As Long
    lpstrFileTitle As String
    nMaxFileTitle As Long
    lpstrInitialDir As String
    lpstrTitle As String
    flags As Long
    nFileOffset As Integer
    nFileExtension As Integer
    lpstrDefExt As String
    lCustData As Long
    lpfnHook As Long
    lpTemplateName As String
End Type
#End If

'//The Win32 API Functions///
#If VBA7 Then
Private Declare PtrSafe Function GetSaveFileName Lib "comdlg32.dll" Alias "GetSaveFileNameA" (pOpenfilename As OPENFILENAME) As Long
Private Declare PtrSafe Function GetOpenFileName Lib "comdlg32.dll" Alias "GetOpenFileNameA" (pOpenfilename As OPENFILENAME) As Long
#Else
Private Declare Function GetSaveFileName Lib "comdlg32.dll" Alias "GetSaveFileNameA" (pOpenfilename As OPENFILENAME) As Long
Private Declare Function GetOpenFileName Lib "comdlg32.dll" Alias "GetOpenFileNameA" (pOpenfilename As OPENFILENAME) As Long
#End If

Global NF As Object
Global strFile As String ' model path

' current folder
Function GetCurDir()
    Dim str As String
    Dim pos As Integer
    str = ThisDrawing.FullName
    pos = InStrRev(str, "\")
    str = Mid(str, 1, pos)
    GetCurDir = str
End Function

'******************************************************************************
'AddLib: Adds a library reference to this script programmatically, so that
'        libraries do not need to be added manually.
'******************************************************************************
Private Function AddLib(libName As String, guid As String, major As Long, minor As Long)
    Dim vbProj As Object
    Set vbProj = Application.VBE.ActiveVBProject
    Dim chkRef As Object
    ' Check if the library has already been added
    For Each chkRef In vbProj.References
        If chkRef.name = libName Then
            GoTo CleanUp
        End If
    Next
    vbProj.References.AddFromGuid guid, major, minor
CleanUp:
    Set vbProj = Nothing
End Function

' variant of previous function for loading from file
Sub AddReference(path As String, name As String)
    Dim VBAEditor As VBIDE.VBE
    Dim vbProj As VBIDE.VBProject
    Dim chkRef As VBIDE.Reference
    Dim BoolExists As Boolean
    Set VBAEditor = Application.VBE
    Set vbProj = Application.VBE.ActiveVBProject
    ' check if it's already added
    For Each chkRef In vbProj.References
        If chkRef.IsBroken Then
            Call vbProj.References.Remove(oRef)
        Else
            If chkRef.name = name Then
                BoolExists = True
                GoTo CleanUp
            End If
        End If
    Next
    vbProj.References.AddFromFile path
CleanUp:
    Set vbProj = Nothing
    Set VBAEditor = Nothing
End Sub

Function ReadRegistry(RootKey, Key As String, Value As String, Optional RegType As Integer = 32) As String
    Dim oCtx, oLocator, oReg, oInParams, oOutParams
    Set oCtx = CreateObject("WbemScripting.SWbemNamedValueSet")
    oCtx.Add "__ProviderArchitecture", RegType
    Set oLocator = CreateObject("Wbemscripting.SWbemLocator")
    Set oReg = oLocator.ConnectServer("", "root\default", "", "", , , , oCtx).Get("StdRegProv")
    Set oInParams = oReg.Methods_("GetStringValue").InParameters
    oInParams.hDefKey = RootKey
    oInParams.sSubKeyName = Key
    oInParams.sValueName = Value
    Set oOutParams = oReg.ExecMethod_("GetStringValue", oInParams, , oCtx)
    ReadRegistry = oOutParams.sValue
End Function

Function regPath() As String
  regPath = ""
  Const rgkey = 2147483650#
  Dim desPath() As String
  desPath = Split(Replace(ReadRegistry(rgkey, "SOFTWARE\Classes\NextFEM Designer\shell\open\command", ""), Chr(34) & Chr(37) & "l" & Chr(34), ""), "\")
  desPath(0) = Replace(desPath(0), Chr(34), "")
  For i = 0 To leng(desPath) - 2
    regPath = regPath & desPath(i) & "\"
  Next
  MsgBox regPath
End Function

Sub loadLib()
    Call AddLib("VBIDE", "{0002E157-0000-0000-C000-000000000046}", 5, 3)
    Call AddReference(regPath & "NextFEMapi.tlb", "NextFEMapi")
    Set NF = CreateObject("NextFEMapi.API")
End Sub

Function leng(obj As Variant) As Integer
    leng = UBound(obj) - LBound(obj) + 1
End Function

Sub openFile()
    loadLib ' run this line if you want to use only this function
    ' open file  + Chr$(0)
    strFile = Replace(ShowOpen("NextFEM model (*.nxf)" + Chr$(0) + "*.nxf", "C:\", "Open NextFEM model"), Chr$(0), "")
    If strFile = "" Then Exit Sub
    
    NF.openModel (strFile)
    
    MsgBox "Loaded model: " & NF.modelName
End Sub

Sub wireframeModel()
    ' draw the loaded wireframe model
    Call openFile
    Dim eList() As String
    eList = NF.elemsList()
    
    For i = 0 To NF.elemsNumber - 1
        Dim tp As String
        tp = NF.getElementProperty(eList(i), "type")
        ' beam
        If tp = 1 Then
            Dim conn() As String
            conn = NF.getElementConnectivity(eList(i))
            ' node 1
            Dim n1 As Object
            Set n1 = NF.getNodePosition(conn(0))
            ' node 2
            Dim n2 As Object
            Set n2 = NF.getNodePosition(conn(1))
            ' draw
            Call drawLine(n1.X, n1.y, n1.z, n2.X, n2.y, n2.z)
        End If
        ' TODO - other types
    Next i
    
End Sub

Sub drawLine(x1 As Double, y1 As Double, z1 As Double, x2 As Double, y2 As Double, z2 As Double)
    Dim pA(0 To 2) As Double
    Dim pB(0 To 2) As Double
    pA(0) = x1: pA(1) = y1: pA(2) = z1
    pB(0) = x2: pB(1) = y2: pB(2) = z2
    With ThisDrawing.ModelSpace
        .AddLine pA, pB
        .Item(.Count - 1).Update
    End With
End Sub

Public Function ShowOpen(Filter As String, InitialDir As String, DialogTitle As String) As String

    Dim OFName As OPENFILENAME
    'Set the structure size
    OFName.lStructSize = LenB(OFName)
    'Set the owner window
    OFName.hwndOwner = 0
    'Set the filter
    OFName.lpstrFilter = Filter
    'Set the maximum number of chars
    OFName.nMaxFile = 255
    'Create a buffer
    OFName.lpstrFile = Space(254)

    'Create a buffer
    OFName.lpstrFileTitle = Space$(254)
    'Set the maximum number of chars
    OFName.nMaxFileTitle = 255
    'Set the initial directory
    OFName.lpstrInitialDir = InitialDir
    'Set the dialog title
    OFName.lpstrTitle = DialogTitle
    'no extra flags
    OFName.flags = 0

    'Show the 'Open File' dialog
    If GetOpenFileName(OFName) Then
        ShowOpen = Trim(OFName.lpstrFile)
    Else
        ShowOpen = ""
    End If

End Function

Sub Show_Userform()
    UserForm1.show
End Sub

Sub runit(name As String)
   Dim Shex As Object
   Set Shex = CreateObject("Shell.Application")
   Shex.Open (name)
End Sub
Sub openAPIref()
    Call runit(regPath & "help\NextFEM API reference.chm")
End Sub

Function NFgetBeamForce(num As Integer, loadcase As String, tp As Integer, station As Integer) As Double
' STATION: a beam has 5 stations (1, 2, 3, 4 or 5)
' TP: 1=N, 2=Vy, 3=Vz, 4=Mt, 5=My, 6=Mz
    NFgetBeamForce = NF.getBeamForce(num, loadcase, "1", tp, station)
End Function

Sub writeNFmodel()
    'loadLib ' run this line if you want to use only this function
    Dim pA(0 To 2) As Double
    pA(0) = x1: pA(1) = y1: pA(2) = z1
    ThisDrawing.ModelSpace.AddText NF.modelName, pA, 1
End Sub

Attribute VB_Name = "UserForm1"
Attribute VB_Base = "0{002336C3-6F94-46D1-958D-664B101F5D09}{4AA3D111-F05A-4C0E-B607-17EE0CE7461F}"
Attribute VB_GlobalNameSpace = False
Attribute VB_Creatable = False
Attribute VB_PredeclaredId = True
Attribute VB_Exposed = False
Attribute VB_TemplateDerived = False
Attribute VB_Customizable = False
Private Sub CommandButton1_Click()
    Call wireframeModel
End Sub

Private Sub CommandButton2_Click()
    Call openAPIref
End Sub
